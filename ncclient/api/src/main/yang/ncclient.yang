module ncclient {
    yang-version 1;
    namespace "urn:opendaylight:params:xml:ns:yang:ncclient";
    prefix "ncclient";

    revision "2017-02-25" {
        description "Initial revision.  Exposes some basic scaffolding to build the ncclient model.";
    }

    grouping unix-command-return {
        leaf output {
            type string;
        }
        leaf error {
            type string;
        }
        leaf returnCode {
            type int32;
        }
    }

    rpc which-python {
        output {
            uses unix-command-return;
        }
    }

    rpc python-version {
        output {
            uses unix-command-return;
        }
    }
}
